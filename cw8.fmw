FME workspace cw8.fmw

Parameters:
- SourceDataset_CSV2 = $(FME_MF_DIR)danecw8\routePoints.csv   # Source CSV (Comma Separated Value) File(s)
- SourceDataset_SHAPEFILE_5 = $(FME_MF_DIR)danecw8\T2019_KAR_POI_TABLE.shp   # Source Esri Shapefile(s)
- SourceDataset_SHAPEFILE_4 = $(FME_MF_DIR)danecw8\T2019_KAR_STREET_NODE.shp   # Source Esri Shapefile(s)
- SourceDataset_SHAPEFILE = $(FME_MF_DIR)danecw8\T2019_KAR_STREETS.shp   # Source Esri Shapefile(s)
- DestDataset_GEOJSON_5 = cw8_6   # Destination GeoJSON File
- DestDataset_GEOJSON = cw8_6   # Destination GeoJSON File
- DestDataset_GEODATABASE_FILE_9 = $(FME_MF_DIR)danecw8\cw8.gdb   # File Geodatabase
- DestDataset_GEODATABASE_FILE = cw8_7   # File Geodatabase
- DestDataset_GEOJSON_6 = $(FME_MF_DIR)danecw8\cw8_7_1.json   # Destination GeoJSON File
- DestDataset_GEOJSON_7 = $(FME_MF_DIR)danecw8\cw8_7_2.json   # Destination GeoJSON File

Readers:
- CSV2_1: CSV2 from $(SourceDataset_CSV2) in EPSG:4326
- SHAPEFILE_1: SHAPEFILE from $(SourceDataset_SHAPEFILE)
- SHAPEFILE_2: SHAPEFILE from $(SourceDataset_SHAPEFILE_5)
- SHAPEFILE_3: SHAPEFILE from $(SourceDataset_SHAPEFILE_4)

Writers:
- GEOJSON_1: GEOJSON to $(DestDataset_GEOJSON)
- GEOJSON_2: GEOJSON to $(DestDataset_GEOJSON_5)
- GEODATABASE_FILE_1: GEODATABASE_FILE to $(DestDataset_GEODATABASE_FILE)
- GEODATABASE_FILE_2: GEODATABASE_FILE to $(DestDataset_GEODATABASE_FILE_9)
- GEOJSON_4: GEOJSON to $(DestDataset_GEOJSON_6)
- GEOJSON_3: GEOJSON to $(DestDataset_GEOJSON_7)

T2019_KAR_POI_TABLE (reader SHAPEFILE_2)
    attributes: POI_ID long, LINK_ID long, TYPE varchar(250), POI_NAME varchar(250), ST_NAME varchar(250), LAT number(31,15), LON number(31,15)
    -> Reprojector_5
Reprojector_5
    DEST = DHDN.Berlin/Cassini
    INTERPOLATION_TYPE_NAME = Nearest Neighbor
    RASTER_CELL_SIZE = Preserve Cells
    RASTER_TOLERANCE = 0.0
    REPROJECTED -> SpatialFilter [Candidate]
    REPROJECTED -> SpatialFilter_2 [Candidate]
T2019_KAR_STREETS (reader SHAPEFILE_1)
    attributes: LINK_ID long, ST_NAME varchar(254), REF_IN_ID long, NREF_IN_ID long, FUNC_CLASS varchar(1), SPEED_CAT varchar(1), FR_SPEED_L long, TO_SPEED_L long, DIR_TRAVEL varchar(1)
    -> Reprojector
Reprojector
    DEST = DHDN.Berlin/Cassini
    INTERPOLATION_TYPE_NAME = Nearest Neighbor
    RASTER_CELL_SIZE = Preserve Cells
    RASTER_TOLERANCE = 0.0
    REPROJECTED -> AttributeFilter
    REPROJECTED -> ShortestPathFinder_3 [NETWORK]
AttributeFilter
    ATTR_NAME = DIR_TRAVEL
    ATTR_VALUES = <Empty>,<Missing>,<Null>,<Unfiltered>,B,F,T
    B -> AttributeCreator
    F -> AttributeCreator_2
    T -> AttributeCreator_3
AttributeCreator
    ATTR_TABLE:
      SET_TO ForwardCost = @Evaluate(1*@Length())
      SET_TO ReverseCost = @Evaluate(1*@Length())
    -> ShortestPathFinder [NETWORK]
AttributeCreator_2
    ATTR_TABLE:
      SET_TO ForwardCost = @Evaluate(1*@Length())
      SET_TO ReverseCost = @Evaluate(9999*@Length())
    -> ShortestPathFinder [NETWORK]
AttributeCreator_3
    ATTR_TABLE:
      SET_TO ForwardCost = @Evaluate(1*@Length())
      SET_TO ReverseCost = @Evaluate(9999*@Length())
    -> ShortestPathFinder [NETWORK]
CSV (reader CSV2_1)
    attributes: x x_coordinate, y y_coordinate
    -> VertexCreator
VertexCreator
    MEASURE_TYPE = Continuous
    MODE_NAME = Replace with Point
    XVAL = @Value(x)
    YVAL = @Value(y)
    -> LineBuilder
LineBuilder
    ACCUM_INPUT_ATTRS = Use Attributes From One Feature
    REMOVE_DUPLICATES = NO
    LINE -> Reprojector_2
    LINE -> zad3
Reprojector_2
    DEST = DHDN.Berlin/Cassini
    INTERPOLATION_TYPE_NAME = Nearest Neighbor
    RASTER_CELL_SIZE = Preserve Cells
    RASTER_TOLERANCE = 0.0
    REPROJECTED -> ShortestPathFinder [FROM-TO]
    REPROJECTED -> ShortestPathFinder_3 [FROM-TO]
ShortestPathFinder
    ALLOW_UTURNS = No
    REORDER_MODE = NONE
    SNAP_POINTS = Yes
    SNAP_TOLERANCE = 200
    WEIGHT_ATTR_1 = ForwardCost
    WEIGHT_ATTR_2 = ReverseCost
    WEIGHT_ATTR_CHOICE = BY_TWO_ATTRIBUTES
    PATH -> Bufferer
    PATH -> LengthCalculator
    PATH -> 5a
Bufferer
    ANGLE = 22.5
    CAP_STYLE = Arc
    CORNER_STYLE = Arc
    MODE = AREA
    OFFSET = 5
    OFFSET_UNITS = METERS
    PRECISION = APPROX
    BUFFERED -> SpatialFilter [Filter]
    BUFFERED -> SpatialFilter_4 [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> geojson_including_cost (writer GEOJSON_4)
geojson_including_cost (writer GEOJSON_4)
    attributes: POI_ID int, LINK_ID int, TYPE string, POI_NAME string, ST_NAME string, LAT float, LON float
LengthCalculator
    DIM = 2
    LEN_ATTR = _length
    MULT = 1
    -> gdb_including_cost (writer GEODATABASE_FILE_2)
5a: Inspector
ShortestPathFinder_3
    ALLOW_UTURNS = Yes
    REORDER_MODE = NONE
    SNAP_POINTS = Yes
    SNAP_TOLERANCE = 200
    WEIGHT_ATTR_CHOICE = BY_LENGTH
    PATH -> Bufferer_2
    PATH -> LengthCalculator_2
    PATH -> 5b
Bufferer_2
    ANGLE = 22.5
    CAP_STYLE = Arc
    CORNER_STYLE = Arc
    MODE = AREA
    OFFSET = 5
    OFFSET_UNITS = METERS
    PRECISION = APPROX
    BUFFERED -> SpatialFilter_2 [Filter]
    BUFFERED -> SpatialFilter_3 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> geojson_no_cost (writer GEOJSON_3)
geojson_no_cost (writer GEOJSON_3)
    attributes: POI_ID int, LINK_ID int, TYPE string, POI_NAME string, ST_NAME string, LAT float, LON float
LengthCalculator_2
    DIM = 2
    LEN_ATTR = _length
    MULT = 1
    -> gdb_no_cost (writer GEODATABASE_FILE_2)
5b: Inspector
zad3: Inspector
T2019_KAR_STREET_NODE (reader SHAPEFILE_3)
    attributes: NODE_ID long, LINK_ID long, POINT_NUM long, Z_LEVEL long, INTERSECT varchar(1), LAT number(31,15), LON number(31,15)
    -> Reprojector_3
Reprojector_3
    DEST = DHDN.Berlin/Cassini
    INTERPOLATION_TYPE_NAME = Nearest Neighbor
    RASTER_CELL_SIZE = Preserve Cells
    RASTER_TOLERANCE = 0.0
    REPROJECTED -> SpatialFilter_3 [Candidate]
    REPROJECTED -> SpatialFilter_4 [Candidate]
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator
StatisticsCalculator
    CALCULATION_MODE = NUMERIC
    FEAT_STATS = LAT,NUMERIC_MODE,MIN,MAX,COUNT,SUM,MEAN,,,,,,,,;LON,NUMERIC_MODE,MIN,MAX,COUNT,SUM,MEAN,,,,,,,,;_total_cost,NUMERIC_MODE,MIN,MAX,COUNT,SUM,MEAN,,,,,,,,;LINK_ID,NUMERIC_MODE,MIN,MAX,COUNT,SUM,MEAN,,,,,,,,;NODE_ID,NUMERIC_MODE,MIN,MAX,COUNT,SUM,MEAN,,,,,,,,;POINT_NUM,NUMERIC_MODE,MIN,MAX,COUNT,SUM,MEAN,,,,,,,,;x,NUMERIC_MODE,MIN,MAX,COUNT,SUM,MEAN,,,,,,,,;y,NUMERIC_MODE,MIN,MAX,COUNT,SUM,MEAN,,,,,,,,;Z_LEVEL,NUMERIC_MODE,MIN,MAX,COUNT,SUM,MEAN,,,,,,,,
    SUMMARY -> gdb_including_cost (writer GEODATABASE_FILE_2)
gdb_including_cost (writer GEODATABASE_FILE_2)
    attributes: x double, y double, _total_cost char(2048), _length double, LAT_min double, LAT_max double, LAT_total_count char(20), LAT_sum double, LAT_mean double, LON_min double, LON_max double, LON_total_count char(20), LON_sum double, LON_mean double, _total_cost_min double, _total_cost_max double, _total_cost_total_count char(20), _total_cost_sum double, _total_cost_mean double, LINK_ID_min integer, LINK_ID_max integer, LINK_ID_total_count char(20), LINK_ID_sum double, LINK_ID_mean double, NODE_ID_min integer, NODE_ID_max integer, NODE_ID_total_count char(20), NODE_ID_sum double, NODE_ID_mean double, POINT_NUM_min integer,
      POINT_NUM_max integer, POINT_NUM_total_count char(20), POINT_NUM_sum double, POINT_NUM_mean double, x_min double, x_max double, x_total_count char(20), x_sum double, x_mean double, y_min double, y_max double, y_total_count char(20), y_sum double, y_mean double, Z_LEVEL_min integer, Z_LEVEL_max integer, Z_LEVEL_total_count char(20), Z_LEVEL_sum double, Z_LEVEL_mean double
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator_2
StatisticsCalculator_2
    CALCULATION_MODE = NUMERIC
    FEAT_STATS = _total_cost,NUMERIC_MODE,MIN,MAX,COUNT,SUM,MEAN,,,,,,,,;LINK_ID,NUMERIC_MODE,MIN,MAX,COUNT,SUM,MEAN,,,,,,,,;NODE_ID,NUMERIC_MODE,MIN,MAX,COUNT,SUM,MEAN,,,,,,,,;POINT_NUM,NUMERIC_MODE,MIN,MAX,COUNT,SUM,MEAN,,,,,,,,;LAT,NUMERIC_MODE,MIN,MAX,COUNT,SUM,MEAN,,,,,,,,;LON,NUMERIC_MODE,MIN,MAX,COUNT,SUM,MEAN,,,,,,,,;x,NUMERIC_MODE,MIN,MAX,COUNT,SUM,MEAN,,,,,,,,;y,NUMERIC_MODE,MIN,MAX,COUNT,SUM,MEAN,,,,,,,,;Z_LEVEL,NUMERIC_MODE,MIN,MAX,COUNT,SUM,MEAN,,,,,,,,
    SUMMARY -> gdb_no_cost (writer GEODATABASE_FILE_2)
gdb_no_cost (writer GEODATABASE_FILE_2)
    attributes: _total_cost_min double, _total_cost_max double, _total_cost_total_count char(20), _total_cost_sum double, _total_cost_mean double, LINK_ID_min integer, LINK_ID_max integer, LINK_ID_total_count char(20), LINK_ID_sum double, LINK_ID_mean double, NODE_ID_min integer, NODE_ID_max integer, NODE_ID_total_count char(20), NODE_ID_sum double, NODE_ID_mean double, POINT_NUM_min integer, POINT_NUM_max integer, POINT_NUM_total_count char(20), POINT_NUM_sum double, POINT_NUM_mean double, LAT_min double, LAT_max double, LAT_total_count char(20), LAT_sum double, LAT_mean double, LON_min double, LON_max double, LON_total_count char(20), LON_sum double, LON_mean double,
      x_min double, x_max double, x_total_count char(20), x_sum double, x_mean double, y_min double, y_max double, y_total_count char(20), y_sum double, y_mean double, Z_LEVEL_min integer, Z_LEVEL_max integer, Z_LEVEL_total_count char(20), Z_LEVEL_sum double, Z_LEVEL_mean double, x double, y double, _total_cost char(2048), _length double
